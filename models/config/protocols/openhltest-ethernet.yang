submodule openhltest-ethernet {
  yang-version 1.1;
  belongs-to openhltest {
    prefix oht;
  }

  import openhltest-patterns {
    prefix p;
  }

  organization
    "OpenHlTest working group";
  contact
    "OpenHlTest working group";
  description
    "This module describes the ethernet emulated protocol.";

  revision 2018-02-09 {
    description
      "Initial revision.";
    reference
      "0.0.1";
  }

  grouping ethernet-group {
    description
      "";
    container ethernet {
      description
        "";
      container mac {
        description
          "The mac address";
        uses p:mac-pattern-group;
      }
    }
  }
}
