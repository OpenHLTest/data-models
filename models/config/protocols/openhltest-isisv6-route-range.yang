submodule openhltest-isisv6-route-range {

    yang-version "1.1";
    belongs-to "openhltest" {
		prefix "oht";
	}

    import openhltest-patterns {
		prefix p;
	}

	organization
      "OpenHlTest working group";
    contact
      "OpenHlTest working group";
    description
      "This module describes the simulated ISIS v6 route range.";

    revision 2018-02-09 {
        description
          "Initial revision.";
        reference
          "0.0.1";
    }
	
	grouping isisv6-route-range-group {
		description "";
		container isisv6-route-range {
			description "";
            leaf active {
                type boolean;
                default "true";
				description "":
            }
            
            container address {
				description "";
                uses p:ipv6-pattern-group;
            }

            container prefix-length {
				description "";
				uses p:base-pattern-group {
					refine pattern-format {
						default "0..32";
					}
					refine single {
						default "24";
					}
				}
            }

            container system-id {
                description
                "System ID.";
				uses p:mac-pattern-group {
					refine single {
						default "00:10:94:00:00:01";
					}
				}
            }
            container sequence-number {
                description
                "Sequence Number. Used to detect old and duplicate LSAs.";
				uses p:base-pattern-group {
					refine single {
						default "80000001";
					}
				}
            }
            container level {
				description
				"This is the circuit type of the emulated router. It defines the type of adjacency 
                Traffic Generator establishes with the DUT..";
                uses p:enum-pattern-group {
                    refine pattern-format {
                        default "(L1|L2|L1L2)";
                    }
                    refine single {
                        default "L2";
                    }
                }
			}
		}
	}
}
