submodule openhltest-bgp4-route-range {

    yang-version "1.1";
    belongs-to "openhltest" {
		prefix "oht";
	}

    import openhltest-patterns {
		prefix p;
	}

	organization
      "OpenHlTest working group";
    contact
      "OpenHlTest working group";
    description
      "This module describes the simulated bgp4 route range.";

    revision 2018-02-09 {
        description
          "Initial revision.";
        reference
          "0.0.1";
    }
	
	grouping bgp4-route-range-group {
		container bgp4-route-range {

            leaf active {
                type boolean;
                default "true";
            }
            
            container address {
                uses p:ipv4-pattern-group {
                    refine single {
                        default "0.0.0.1";
                    }
                }
            }

            container prefix-length {
				uses p:base-pattern-group {
					refine pattern-format {
						default "0..32";
					}
					refine single {
						default "24";
					}
				}
            }

            container as-path {
                description
                "Used in the AS_PATH attribute in BGP UPDATE messages.";
				uses p:base-pattern-group {
					refine pattern-format {
						default "0..2147483647";
					}
					refine single {
						default "1";
					}
				}
            }

			container next-hop-address {
				description
				"The next hop is the node to which packets should be sent to get them closer 
                to the destination. Specify the IP address of the border router that should be 
                used as the next hop to the destinations listed in the UPDATE message. 
                This is the mandatory NEXT_HOP path attribute in UPDATE messages.";
                uses p:ipv4-pattern-group;
			}
            
            container aigp-metric {
                description
                "Value of the first accumulated interior gateway protocol(AIGP) metric";
				uses p:int-64-pattern-group {
					refine single {
						default "10";
					}
				}
            }
            
            container atomic-aggregate {
                presence
                    "Indicates whether to include the ATOMIC_AGGREGATE attribute in BGP UPDATE messages";
                container aggregate-as {
                    description
                    "The AS number to use for the AGGREGATOR attribute";
                    uses p:int-64-pattern-group;
                }
                container aggregate-ip {
                    description
                    "The IP address to use for the AGGREGATOR attribute.";
                    uses p:ipv4-pattern-group;
                }
            }
		}
	}
}
