submodule openhltest-ospfv3-route-range {
  yang-version 1.1;
  belongs-to openhltest {
    prefix oht;
  }

  import openhltest-types {
    prefix t;
  }
  import openhltest-patterns {
    prefix p;
  }

  organization
    "OpenHlTest working group";
  contact
    "OpenHlTest working group";
  description
    "This module describes the simulated OSPFV3 Router LSA range.";

  revision 2018-02-09 {
    description
      "Initial revision.";
    reference
      "0.0.1";
  }

  grouping ospfv3-route-range-group {
    description
      "";
    container ospfv3-route-range {
      description
        "";
      leaf active {
        type boolean;
        default "true";
        description
          "";
      }
      container advertise-router-id {
        description
          "Advertising Router ID.  Specifies the 32-bit router ID of the router that
           advertises a given LSA ";
        uses p:ipv4-pattern-group;
      }
      container router-type {
        description
          "Router Type
           ASBR    : AS Boundary Router (E-bit set)
           ABR     : Border Router (B-bit set)";
        uses p:enum-pattern-group {
          refine "pattern-format" {
            default "(ABR|ASBR)";
          }
          refine "single" {
            default "ABR";
          }
        }
      }
      container sequence-number {
        description
          "Sequence Number. Used to detect old and duplicate LSAs.";
        uses p:base-pattern-group {
          refine "single" {
            default "80000001";
          }
        }
      }
      container age {
        description
          "Age of the LSA, in seconds.";
        uses p:base-pattern-group {
          refine "pattern-format" {
            default "0..3600";
          }
          refine "single" {
            default "0";
          }
        }
      }
      list ospfv3-router-link {
        key "name";
        description
          "";
        leaf name {
          type t:config-list-key;
          description
            "The unique name of the networks object.";
        }
        container router-link-type {
          description
            "Type of link
             VIRTUAL_LINK   : Virtual Link
             POINT_TO_POINT : P2P (point-to-point) adjacency";
          uses p:enum-pattern-group {
            refine "pattern-format" {
              default "(POINT_TO_POINT|VIRTUAL_LINK)";
            }
            refine "single" {
              default "POINT_TO_POINT";
            }
          }
        }
        container interface-id {
          description
            "The Interface ID is an interface index number that a router uses to uniquely
             identify an interface. The Interface ID must be unique within the router.";
          uses p:int-32-pattern-group {
            refine "single" {
              default "0";
            }
          }
        }
      }
    }
  }
}
