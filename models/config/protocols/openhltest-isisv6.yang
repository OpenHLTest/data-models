submodule openhltest-isisv6 {

    yang-version "1.1";
    belongs-to "openhltest" {
		prefix "oht";
	}
    
	/*import ietf-inet-types {
		prefix inet;
	}*/
    import openhltest-patterns {
		prefix p;
	}
	organization
      "OpenHlTest working group";
    contact
      "OpenHlTest working group";
    description
      "This module describes the isisv6 emulated protocol.";

    revision 2018-02-09 {
        description
          "Initial revision.";
        reference
          "0.0.1";
    }

	grouping isisv6-group {
		description "";
		container isisv6 {
			description "";
            container system-id {
                description
                "The System ID is used to identify an emulated router.";
                uses p:mac-pattern-group;
            }
            
            container network-type {
				description
				"This setting to override the physical link type to emulate a broadcast 
                adjacency over POS, or a point-to-point adjacency over Ethernet
                BROADCAST : Broadcast adjacency
                P2P       : P2P (point-to-point) adjacency";
                uses p:enum-pattern-group {
                    refine pattern-format {
                        default "(BROADCAST|P2P)";
                    }
                    refine single {
                        default "BROADCAST";
                    }
                }
			}
            
            container router-priority {
				description
				"Router priority of the emulated router. Set the router priority to a higher 
                or lower value to influence the DR and BDR selection process.";
				uses p:int-32-pattern-group;
			}
            container level {
				description
				"This is the circuit type of the emulated router. It defines the type of adjacency 
                Traffic Generator establishes with the DUT..";
                uses p:enum-pattern-group {
                    refine pattern-format {
                        default "(L1|L2|L1L2)";
                    }
                    refine single {
                        default "L2";
                    }
                }
			}
            container hello-interval {
				description
				"Time interval (in seconds) used by the emulated routers to pace Hello packet 
                transmissions.";
                uses p:base-pattern-group {
                    refine pattern-format {
                        default "0..65535";
                    }
                    refine single {
                        default "10";
                    }
                }
			}
            container authentication {
                presence
                    "Type of authentication to be used
                    NONE   : no authentication
                    SIMPLE : The packet is authenticated by the receiving router if the password 
                             matches the authentication key that is included in the packet. 
                             This method provides little security because the authentication
                             key can be learned by capturing packets.
                    MD5    : The packet contains a cryptographic checksum, but not the authentication
                            key itself. The receiving router performs a calculation based on the 
                            MD5 algorithm and an authentication key ID. The packet is authenticated
                            if the calculated checksum matches. This method provides a stronger
                            assurance that routing data originated from a router with a valid 
                            authentication key.";
				description "";
                container authentication-type {
                    description
                    "Type of authentication to be used";
                    uses p:enum-pattern-group {
                        refine pattern-format {
                            default "(SIMPLE|MD5|NONE)";
                        }
                        refine single {
                            default "NONE";
                        }
                    }
                }
                container password {
                    description
                    "Authentication password.";
                    uses p:string-pattern-group;
                }
            }
		}
	}
}
