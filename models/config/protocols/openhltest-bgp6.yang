submodule openhltest-bgp6 {

    yang-version "1.1";
    belongs-to "openhltest" {
		prefix "oht";
	}
    
    import openhltest-patterns {
		prefix p;
	}
    include openhltest-bgp-common;

	organization
      "OpenHlTest working group";
    contact
      "OpenHlTest working group";
    description
      "This module describes the bgp6 emulated protocol.";

    revision 2018-02-09 {
        description
          "Initial revision.";
        reference
          "0.0.1";
    }

	grouping bgp6-group {
		container bgp6 {
			uses bgp-common-group;

            container dut-ipv6-address {
				description
				"Ipv6 address of the BGP peer for the session.";
				uses p:ipv6-pattern-group;
			}
		}
	}
}
