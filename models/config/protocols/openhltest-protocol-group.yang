submodule openhltest-protocol-group {

    yang-version "1.1";
    belongs-to "openhltest" {
		prefix "oht";
	}

    import openhltest-types {
        prefix t;
    }
	
	organization
      "OpenHlTest working group";
    contact
      "OpenHlTest working group";
    description
      "This module describes a collection of emulated protocols
	  and associated rpcs.";

    revision 2018-02-09 {
        description
          "Initial revision.";
        reference
          "0.0.1";
    }

    grouping protocol-group-top {
        description
        "A reuseable grouping of emulated protocols.
		 A protocol group is a collection of emulated protocols sharing the 
		 same group level scaling features.";

		list protocol-groups {
			key "name";
			description
			"A list of emulated protocol groups";

			leaf name {
				type string;
				description
				"The unique name of an emulated protocol group";
			}

			leaf-list port-names {
				description 
				"A list of abstract test port names";
				type string;
			}
		}

		action start-protocols {
			description
			"Start one or more emulated protocol groups.
			An empty list signifies that all protocol groups will be started.";

			input {
				leaf-list protocol-group-names {
					description "A list of protocol group names";
					type string;
				}
			}
			output {
				uses t:errata-group {
					description "A list of protocol group resources that failed to start.
					An empty list signifies that all protocol groups successfully started.";
				}
			}
		}
		action stop-protocols {
			description
			"Stop one or more protocol groups. 
			An empty list signifiels that all protocol groups will be stopped.";

			input {
				leaf-list protocol-group-names {
					description "A list of protocol group names";
					type string;
				}
			}
			output {
				uses t:errata-group {
					description "A list of protocol group resources that failed to stop.
					An empty list signifies that all protocol groups successfully stopped.";
				}
			}
		}
	}
}
