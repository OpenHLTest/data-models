submodule openhltest-bgpv6 {
  yang-version 1.1;
  belongs-to openhltest {
    prefix oht;
  }

  import openhltest-patterns {
    prefix p;
  }
  include openhltest-bgp-common;

  organization
    "OpenHlTest working group";
  contact
    "OpenHlTest working group";
  description
    "This module describes the bgpv6 emulated protocol.";

  revision 2018-02-09 {
    description
      "Initial revision.";
    reference
      "0.0.1";
  }

  grouping bgpv6-group {
    description
      "";
    container bgpv6 {
      description
        "";
      uses bgp-common-group;
      container dut-ipv6-address {
        description
          "Ipv6 address of the BGP peer for the session.";
        uses p:ipv6-pattern-group;
      }
    }
  }
}
