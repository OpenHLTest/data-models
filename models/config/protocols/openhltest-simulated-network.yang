submodule openhltest-simulated-network {

    yang-version "1.1";
    belongs-to "openhltest" {
		prefix "oht";
	}

	import ietf-yang-types {
		prefix yang;
	}
	include opehltest-device-groups;
	include openhltest-ipv4-route-range;
	include openhltest-bgp4-route-range;

	organization
      "OpenHlTest working group";
    contact
      "OpenHlTest working group";
    description
      "This module describes the simulated networks used by device-groups.";

    revision 2018-02-09 {
        description
          "Initial revision.";
        reference
          "0.0.1";
    }
	
	grouping simulated-network-group {
		list simulated-networks {
			key "name";
			leaf "name" {
				type string;
			}
			leaf-list connections {
				type leafref {
					path "/device-groups/devices/protocols";
				}
			}
			leaf simulated-type {
				enumeration {
					enum "IPV4_ROUTE_RANGE";
					enum "BGP4_ROUTE_RANGE";
				}
			}
			uses ipv4-route-range-group {
				when "../simulated-type = IPV4_ROUTE_RANGE";
			}
			uses bgpv4-route-range-group {
				when "../simulated-type = BGPV4_ROUTE_RANGE";
			}
		}
	}
}
