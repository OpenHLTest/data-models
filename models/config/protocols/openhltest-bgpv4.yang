submodule openhltest-bgpv4 {
  yang-version 1.1;
  belongs-to openhltest {
    prefix oht;
  }

  import openhltest-patterns {
    prefix p;
  }
  include openhltest-bgp-common;

  organization
    "OpenHlTest working group";
  contact
    "OpenHlTest working group";
  description
    "This module describes the bgpv4 emulated protocol.";

  revision 2018-02-09 {
    description
      "Initial revision.";
    reference
      "0.0.1";
  }

  grouping bgpv4-group {
    description
      "";
    container bgpv4 {
      description
        "";
      uses bgp-common-group;
      container dut-ipv4-address {
        description
          "IPv4 address of the BGP peer for the session.";
        uses p:ipv4-pattern-group;
      }
    }
  }
}
