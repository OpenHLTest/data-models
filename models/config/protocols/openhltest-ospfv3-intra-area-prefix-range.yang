submodule openhltest-ospfv3-intra-area-prefix-range {
  yang-version 1.1;
  belongs-to openhltest {
    prefix oht;
  }

  import openhltest-patterns {
    prefix p;
  }

  organization
    "OpenHlTest working group";
  contact
    "OpenHlTest working group";
  description
    "This module describes the simulated OSPFV3 intra-Area Prefix LSA range.";

  revision 2018-02-09 {
    description
      "Initial revision.";
    reference
      "0.0.1";
  }

  grouping ospfv3-intra-area-prefix-range-group {
    description
      "";
    container ospfv3-intra-area-prefix-range {
      description
        "";
      container address {
        description
          "IPv6 address";
        uses p:ipv6-pattern-group {
          refine "single" {
            default "2000::1";
          }
        }
      }
      container prefix-length {
        description
          "Prefix Length";
        uses p:base-pattern-group {
          refine "pattern-format" {
            default "0..128";
          }
          refine "single" {
            default "64";
          }
        }
      }
      container advertise-router-id {
        description
          "Advertising Router ID.  Specifies the 32-bit router ID of the router that
           advertises a given LSA ";
        uses p:ipv4-pattern-group;
      }
      container sequence-number {
        description
          "Sequence Number. Used to detect old and duplicate LSAs.";
        uses p:base-pattern-group {
          refine "single" {
            default "80000001";
          }
        }
      }
      container age {
        description
          "Age of the LSA, in seconds.";
        uses p:base-pattern-group {
          refine "pattern-format" {
            default "0..3600";
          }
          refine "single" {
            default "0";
          }
        }
      }
      container checksum {
        description
          "Specifies the LSA will be advertised with a good or a bad checksum.";
        uses p:enum-pattern-group {
          refine "pattern-format" {
            default "(GOOD|BAD)";
          }
          refine "single" {
            default "GOOD";
          }
        }
      }
      container route-category {
        description
          "Route Category can be used to filter routes by type.
              UNDEFINED The default category assigned to a manually created block.
              PRIMARY   A preferred route that has duplicates (secondary routes) advertised by other ports.
              SECONDARY Secondary route.
              UNIQUE    A less preferred backup route.
              ANY       Indicates that a single port in the test configuration advertises this route.";
        uses p:enum-pattern-group {
          refine "pattern-format" {
            default "(UNDEFINED|PRIMARY|SECONDARY|UNIQUE|ANY)";
          }
          refine "single" {
            default "UNDEFINED";
          }
        }
      }
      container metric {
        description
          "Cost of the advertised network prefix.";
        uses p:base-pattern-group {
          refine "pattern-format" {
            default "0..16777215";
          }
          refine "single" {
            default "1";
          }
        }
      }
      container prefix-options {
        description
          "8- bit field of capabilities advertised with each prefix.
              NUBIT    No Unicast capability bit. If set, the prefix is excluded from IPv6 unicast calculations.
              LABIT    Local Address capability bit. If set, the prefix becomes an IPv6 interface address of the advertising router.
              MCBIT    Multicast capability bit. If set, the prefix is included in the IPv6 multicast calculations.
              PBIT     Propagate bit. Set this on the NSSA area prefixes that should be readvertised at the NSSA border.
              DNBIT    Downward bit. Controls an inter-area-prefix-LSAs or AS-external-LSAs re-advertisement in a VPN environment
              NBIT     Set in PrefixOptions for a host address (PrefixLength=128) that identifies the advertising router
              UNUSED6  Bit not defined.
              UNUSED7  Bit not defined. ";
        uses p:base-pattern-group {
          refine "single" {
            default "0";
          }
        }
      }
      container link-state-id {
        description
          "Link State ID. ID of the interface connected to the transit network";
        uses p:base-pattern-group {
          refine "pattern-format" {
            default "0..65535";
          }
          refine "single" {
            default "0";
          }
        }
      }
      container referenced-lsa {
        description
          "";
        container type {
          description
            "Type of the referenced LSA.";
          uses p:base-pattern-group {
            refine "pattern-format" {
              default "0..65535";
            }
            refine "single" {
              default "0";
            }
          }
        }
        container advertise-router-id {
          description
            "Router ID of the router that originated the LSA or the Designated Router ";
          uses p:ipv4-pattern-group;
        }
        container link-state-id {
          description
            "Referenced Link State ID.";
          uses p:base-pattern-group {
            refine "pattern-format" {
              default "0..65535";
            }
            refine "single" {
              default "0";
            }
          }
        }
      }
    }
  }
}
