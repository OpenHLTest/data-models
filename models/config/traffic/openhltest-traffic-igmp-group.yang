submodule openhltest-traffic-igmp-group {
  yang-version 1.1;
  belongs-to openhltest {
    prefix oht;
  }

  import openhltest-types {
    prefix t;
  }
  import openhltest-patterns {
    prefix p;
  }

  organization
    "OpenHlTest working group";
  contact
    "OpenHlTest working group";
  description
    "This module describes a collection of igmp message formats.";

  revision 2018-02-09 {
    description
      "Initial revision.";
    reference
      "0.0.1";
  }

  grouping traffic-igmp-group-top {
    description
      "A grouping of IGMP message formats.";
    uses traffic-igmpv1-query-top;
    uses traffic-igmpv1-report-top;
    uses traffic-igmpv2-query-top;
    uses traffic-igmpv2-report-top;
    uses traffic-igmpv3-query-top;
    uses traffic-igmpv3-report-top;
  }

  grouping traffic-igmpv1-query-top {
    description
      "A grouping of IGMPv1 Query message format.";
    container igmpv1-query {
      description
        "IGMPv1 Query message";
      container group-address {
        description
          "Group IPv4 Address";
        uses p:ipv4-pattern-group {
          refine "single" {
            default "225.0.0.1";
          }
        }
      }
      container checksum {
        description
          "Checksum value.";
        uses p:int-32-pattern-group {
          refine "single" {
            default "0";
          }
        }
      }
      container unused {
        description
          "Unused.";
        uses p:int-32-pattern-group {
          refine "single" {
            default "0";
          }
        }
      }
    }
  }

  grouping traffic-igmpv1-report-top {
    description
      "A grouping of IGMPv1 Report message format.";
    container igmpv1-report {
      description
        "IGMPv1 Report message";
      container group-address {
        description
          "Group IPv4 Address";
        uses p:ipv4-pattern-group {
          refine "single" {
            default "225.0.0.1";
          }
        }
      }
      container checksum {
        description
          "Checksum value.";
        uses p:int-32-pattern-group {
          refine "single" {
            default "0";
          }
        }
      }
      container unused {
        description
          "Unused.";
        uses p:int-32-pattern-group {
          refine "single" {
            default "0";
          }
        }
      }
    }
  }

  grouping traffic-igmpv2-query-top {
    description
      "A grouping of IGMPv2 Query message format.";
    container igmpv2-query {
      description
        "IGMPv2 Query message";
      container group-address {
        description
          "Group IPv4 Address";
        uses p:ipv4-pattern-group {
          refine "single" {
            default "225.0.0.1";
          }
        }
      }
      container checksum {
        description
          "Checksum value.";
        uses p:int-32-pattern-group {
          refine "single" {
            default "0";
          }
        }
      }
      container max-response-time {
        description
          "Maximum response Time.";
        uses p:int-32-pattern-group {
          refine "single" {
            default "100";
          }
        }
      }
    }
  }

  grouping traffic-igmpv2-report-top {
    description
      "A grouping of IGMPv2 Report message format.";
    container igmpv2-report {
      description
        "IGMPv2 Report message";
      container group-address {
        description
          "Group IPv4 Address";
        uses p:ipv4-pattern-group {
          refine "single" {
            default "225.0.0.1";
          }
        }
      }
      container checksum {
        description
          "Checksum value.";
        uses p:int-32-pattern-group {
          refine "single" {
            default "0";
          }
        }
      }
      container max-response-time {
        description
          "Maximum response Time.";
        uses p:int-32-pattern-group {
          refine "single" {
            default "100";
          }
        }
      }
    }
  }

  grouping traffic-igmpv3-query-top {
    description
      "A grouping of IGMPv3 Query message format.";
    container igmpv3-query {
      description
        "IGMPv3 Query message";
      container group-address {
        description
          "Group IPv4 Address";
        uses p:ipv4-pattern-group {
          refine "single" {
            default "225.0.0.1";
          }
        }
      }
      container checksum {
        description
          "Checksum value.";
        uses p:int-32-pattern-group {
          refine "single" {
            default "0";
          }
        }
      }
      container max-response-time {
        description
          "Maximum response Time.";
        uses p:int-32-pattern-group {
          refine "single" {
            default "100";
          }
        }
      }
      container number-of-sources {
        description
          "Number of Sources.";
        uses p:int-32-pattern-group {
          refine "single" {
            default "100";
          }
        }
      }
      container suppress-flag {
        description
          "Suppress Flag.";
        uses p:binary-pattern-group {
          refine "single" {
            default "1";
          }
        }
      }
      container reserved {
        description
          "Reserved.";
        uses p:int-32-pattern-group {
          refine "single" {
            default "0";
          }
        }
      }
      container qqic {
        description
          "QQIC(Querier's Query Interval Code).";
        uses p:int-32-pattern-group {
          refine "single" {
            default "0";
          }
        }
      }
      container qrv {
        description
          "QRV bits(Querier's Robustness Variable).";
        uses p:base-pattern-group {
          refine "single" {
            default "000";
          }
        }
      }
      list source-address-list {
        key "name";
        description
          "";
        leaf name {
          type t:config-list-key;
          description
            "";
        }
        container address {
          description
            "Source IPv4 Address";
          uses p:ipv4-pattern-group {
            refine "single" {
              default "192.0.0.1";
            }
          }
        }
      }
    }
  }

  grouping traffic-igmpv3-report-top {
    description
      "A grouping of IGMPv3 Report message format.";
    container igmpv3-report {
      description
        "IGMPv3 Report message";
      container checksum {
        description
          "Checksum value.";
        uses p:int-32-pattern-group {
          refine "single" {
            default "0";
          }
        }
      }
      container number-of-group-records {
        description
          "Number of group records.";
        uses p:int-32-pattern-group {
          refine "single" {
            default "0";
          }
        }
      }
      container reserved {
        description
          "Reserved";
        uses p:int-32-pattern-group {
          refine "single" {
            default "0";
          }
        }
      }
      container reserved2 {
        description
          "Reserved2";
        uses p:int-32-pattern-group {
          refine "single" {
            default "0";
          }
        }
      }
    }
  }
}
