submodule openhltest-traffic-group {

    yang-version "1.1";
    belongs-to "openhltest" {
		prefix "oht";
	}

    import openhltest-types {
        prefix t;
    }
	
    include openhltest-traffic-frame-options;
    include openhltest-traffic-ethernet-group;
    include openhltest-traffic-vlan-group;
    include openhltest-traffic-ipv4-group;
    include openhltest-traffic-ipv6-group;
    include openhltest-traffic-tcp-group;
    include openhltest-traffic-udp-group;
    
    organization
      "OpenHlTest working group";
    contact
      "OpenHlTest working group";
    description
      "This module describes a collection of traffic groups
	  and associated rpcs.";

    revision 2018-02-09 {
        description
          "Initial revision.";
        reference
          "0.0.1";
    }

    grouping traffic-group-top {
        description
        "A grouping of traffic groups.
		 A traffic group is a collection of traffic streams and flows.";
		
		list traffic-groups {
			key "name";
			description
			"A list of traffic groups";

			leaf name {
				type t:config-list-key;
				description
				"The unique name of a traffic group";
			}

			leaf bidirectional {
				type boolean;
				default false;
				description
				"Direction of traffic flow between two end points";
			}
			leaf mesh-type {
				description
				"The type of mapping between sources and destinations endpoints.";
				default "ONE_TO_ONE";
				type enumeration {
					enum ONE_TO_ONE;
					enum FULL_MESHED;
				}
			}
			leaf encapsulation {
				description "The encapsulation determines what the generated-flows list will contain based on the sources and destinations.
				Any time an update is done on any one or more of encapsulation, sources or destinations the generated-flows list can possibly change.";
				type enumeration {
					enum RAW;
					enum ETHERNET;
					enum VLAN;
					enum IPV4;
					enum IPV6;
				}
				default "RAW";
			}

			leaf-list source-endpoints {
				description "List of 1..n abstract ports, device-groups, devices, protocols references.";
				type union {
					type leafref {
						path "../../../ports/name";
					}
					type leafref {
						path "../../../device-groups/name";
					}
					type leafref {
						path "../../../device-groups/devices/name";
					}
					type leafref {
						path "../../../device-groups/devices/protocols/name";
					}
				}
			}

			leaf-list destination-endpoints {
				description "List of 0..n abstract ports, device-groups, devices, protocols references.
				If the mesh-type is FULLY_MESHED then sources and destinations should be merged and any duplicates will be ignored.";
				type union {
					type leafref {
						path "../../../ports/name";
					}
					type leafref {
						path "../../../device-groups/name";
					}
					type leafref {
						path "../../../device-groups/devices/name";
					}
					type leafref {
						path "../../../device-groups/devices/protocols/name";
					}
				}
			}
            uses traffic-frame-options-group;

            list user-frames {
				key "name";
				description "List of user defined frames. 
				Changing the encapsulation will clear the list of custom frames.";
				leaf name {
					type t:config-list-key;
				}
                uses traffic-ethernet-group-top;
                uses traffic-vlan-group-top;
                uses traffic-ipv4-group-top;
                uses traffic-ipv6-group-top;
                uses traffic-tcp-group-top;
		uses traffic-udp-group-top;
            }
            
		}

		action start-traffic {
			description
			"Start one or more traffic groups.
			An empty list signifies that all traffic groups will be started.";

			input {
				leaf-list traffic-group-names {
					description "A list of traffic group names";
					type string;
				}
			}
			output {
				uses t:errata-group {
					description "A list of traffic group resources that failed to start.
					An empty list signifies that all traffic groups successfully started.";
				}
			}
		}
		action stop-traffic {
			description
			"Stop one or more traffic groups. 
			An empty list signifies that all traffic groups will be stopped.";

			input {
				leaf-list traffic-group-names {
					description "A list of traffic group names";
					type string;
				}
			}
			output {
				uses t:errata-group {
					description "A list of traffic group resources that failed to start.
					An empty list signifies that all traffic groups successfully stopped.";
				}
			}
		}
    }
}
