submodule openhltest-traffic-protocols {

	yang-version "1.1";
	belongs-to "openhltest" {
		prefix "oht";
	}

	import ietf-yang-types {
		prefix iyt;
	}
	import openhltest-types {
		prefix t;
	}
	import openhltest-patterns {
		prefix p;
	}
	// include openhltest-ethernet;
	// include openhltest-vlan;
	// include openhltest-ipv4;
	// include openhltest-bgp4;
	// include openhltest-bgp6;
	// include openhltest-port;
	// include openhltest-bgp4-route-range;

	organization
	"OpenHlTest working group";
	contact
	"OpenHlTest working group";
	description
	"This module describes a collection of traffic protocols.";

	revision 2018-02-09 {
		description
		  "Initial revision.";
		reference
		  "0.0.1";
	}

	grouping traffic-protocols-group {
		description
		"A grouping of all possible traffic protocols.";
		leaf protocol-type {
			type enumeration {
				enum ETHERNET;
				enum VLAN;
				enum IPV4;
				enum IPV6;
				enum TCP;
				enum UDP;
			}
		}
		uses ethernet-frame-group {
			description "The conditional container for detailed ethernet information";
			when "../protocol-type = ETHERNET";
		}
		// uses vlan-frame-group {
		// 	description "The conditional container for detailed vlan information"; 
		// 	when "../protocol-type = VLAN";
		// }
		uses ipv4-frame-group {
			description "The conditional container for detailed ipv4 information"; 
			when "../protocol-type = IPV4";
		}
		// uses ipv6-frame-group {
		// 	description "The conditional container for detailed ipv6 information"; 
		// 	when "../protocol-type = IPV6";
		// }
		// uses tcp-frame-group {
		// 	description "The conditional container for detailed tcp information"; 
		// 	when "../protocol-type = TCP";
		// }
		// uses udp-frame-group {
		// 	description "The conditional container for detailed udp information"; 
		// 	when "../protocol-type = UDP";
		// }
		uses custom-frame-group {
			description "The conditional container for custom frame information";
			when "../protocol-type = CUSTOM";
		}
	}
	grouping ethernet-frame-group {
		container ethernet {
			container destination {
				presence "Create the destination container to override the automatic destination mac address";
				uses p:mac-pattern-group;
				leaf count {
					type int32;
				}
			}
			container source {
				presence "Create the source container to override the automatic source mac address";
				uses p:mac-pattern-group;
				leaf count {
					type int32;
				}
			}
			container fcs {
				presence "Create the fcs container to override the automatic frame check sequence value.";
				uses p:hex-pattern-group;
				leaf count {
					type int32;
				}
			}
		}
	}
	grouping ipv4-frame-group {
		container ipv4 {
			container destination {
				uses p:ipv4-pattern-group;
			}
			container source {
				uses p:ipv4-pattern-group;
			}
		}
	}
	grouping custom-frame-group {
		container custom {
			leaf payload-type {
				type enumeration {
					enum INCREMENT_BYTE;
					enum DECREMENT_BYTE;
					enum INCREMENT_WORD;
					enum DECREMENT_WORD;
					enum CRPAT;
					enum CJPAT;
					enum RANDOM;
					enum CUSTOM;
				}
			}
			container payload {
				leaf data {
					when "../payload-type = CUSTOM";
					type iyt:hex-string;
					default "00";
				}
				leaf repeat {
					description "Repeat the payload data to fill the length specified";
					type boolean;
					default "false";
				}
				leaf length {
					type int32;
					default 0;
				}
			}
		}
	}
}
