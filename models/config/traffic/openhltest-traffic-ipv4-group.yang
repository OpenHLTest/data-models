submodule openhltest-traffic-ipv4-group {
  yang-version 1.1;
  belongs-to openhltest {
    prefix oht;
  }

  import openhltest-patterns {
    prefix p;
  }

  organization
    "OpenHlTest working group";
  contact
    "OpenHlTest working group";
  description
    "This module describes a collection of traffic groups
     and associated rpcs.";

  revision 2018-02-09 {
    description
      "Initial revision.";
    reference
      "0.0.1";
  }

  grouping traffic-ipv4-group-top {
    description
      "A grouping of traffic groups.
       A traffic group is a collection of traffic streams and flows.";
    container ipv4 {
      description
        "";
      container source-address {
        description
          "Source IPv4 Address";
        uses p:ipv4-pattern-group;
      }
      container destination-address {
        description
          "Destination IPv4 Address";
        uses p:ipv4-pattern-group;
      }
      container ttl {
        description
          "The limited number of iterations that a unit of data can experience before
                      the data is discarded.";
        uses p:base-pattern-group {
          refine "pattern-format" {
            default "0..255";
          }
          refine "single" {
            default "255";
          }
        }
      }
      container header-length {
        description
          "The length of the IP header field in number of bytes.";
        uses p:int-32-pattern-group {
          refine "pattern-format" {
            default "0..15";
          }
          refine "single" {
            default "5";
          }
        }
      }
      container identification {
        description
          "Specifies the identifying value used to help assemble the fragments of a datagram.";
        uses p:int-32-pattern-group {
          refine "pattern-format" {
            default "0..65535";
          }
          refine "single" {
            default "0";
          }
        }
      }
      container fragment-offset {
        description
          "The byte count from the start of the original sent packet.";
        uses p:int-32-pattern-group {
          refine "pattern-format" {
            default "0..8191";
          }
          refine "single" {
            default "0";
          }
        }
      }
      container protocol {
        description
          "Indicates the type of L4 protocol in the IP header.";
        uses p:int-32-pattern-group {
          refine "pattern-format" {
            default "0..255";
          }
          refine "single" {
            default "253";
          }
        }
      }
      container checksum {
        description
          "Verifies that packets are not corrupted.";
        uses p:enum-pattern-group {
          refine "pattern-format" {
            default "(0|1)";
          }
          refine "single" {
            default "1";
          }
        }
      }
      container reserved-bit {
        description
          "Specifies the reserved bit in the Flags field of the internet header.";
        uses p:base-pattern-group {
          refine "pattern-format" {
            default "0..1";
          }
          refine "single" {
            default "0";
          }
        }
      }
      container mf-bit {
        description
          "Specifies the More Fragment (MF) bit in the Flags field of the internet header.";
        uses p:base-pattern-group {
          refine "pattern-format" {
            default "0..1";
          }
          refine "single" {
            default "0";
          }
        }
      }
      container df-bit {
        description
          "Specifies whether the datagram is fragmented.";
        uses p:base-pattern-group {
          refine "pattern-format" {
            default "0..1";
          }
          refine "single" {
            default "0";
          }
        }
      }
    }
  }
}
