submodule openhltest-traffic-udp-group {
  yang-version 1.1;
  belongs-to openhltest {
    prefix oht;
  }

  import openhltest-patterns {
    prefix p;
  }

  organization
    "OpenHlTest working group";
  contact
    "OpenHlTest working group";
  description
    "This module describes a collection of traffic groups
     and associated rpcs.";

  revision 2018-02-09 {
    description
      "Initial revision.";
    reference
      "0.0.1";
  }

  grouping traffic-udp-group-top {
    description
      "A grouping of traffic groups.
       A traffic group is a collection of traffic streams and flows.";
    container udp {
      description
        "";
      container source-port {
        description
          "Specifies the port on the sending UDP module.";
        uses p:int-32-pattern-group;
      }
      container destination-port {
        description
          "Specifies the port on the receiving UDP module.";
        uses p:int-32-pattern-group;
      }
      container checksum {
        description
          "Specifies the UDP checksum value.";
        uses p:int-32-pattern-group;
      }
    }
  }
}
