submodule openhltest-traffic-endpoints {

    yang-version "1.1";
    belongs-to "openhltest" {
        prefix "oht";
    }

    import openhltest-types {
        prefix t;
    }
    import openhltest-extensions {
        prefix e;
    }
    include openhltest-ports;
    include openhltest-device-groups;

    organization
      "OpenHlTest working group";
    contact
      "OpenHlTest working group";
    description
      "This module describes a collection of traffic endpoints
      and associated rpcs.";

    revision 2018-02-09 {
        description
          "Initial revision.";
        reference
          "0.0.1";
    }

}
