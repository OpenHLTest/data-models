submodule openhltest-traffic-groups {

    yang-version "1.1";
    belongs-to "openhltest" {
        prefix "oht";
    }

    import openhltest-types {
        prefix t;
    }
    import openhltest-extensions {
        prefix e;
    }
    include openhltest-traffic-endpoints;
    include openhltest-traffic-frame-options;
    include openhltest-traffic-ethernet-group;
    include openhltest-traffic-frame-group;
    include openhltest-ports;
    include openhltest-device-groups;

    organization
      "OpenHlTest working group";
    contact
      "OpenHlTest working group";
    description
      "This module describes a collection of traffic groups
      and associated rpcs.";

    revision 2018-02-09 {
        description
          "Initial revision.";
        reference
          "0.0.1";
    }

    grouping traffic-group-top {
        description "A grouping of traffic groups.";
        
        list traffic-groups {
            description "A traffic-groups object acts as a wizard in that the object generates one or more traffic-streams objects.

            The following traffic-groups criteria acts as a template for the generated traffic-streams:
                mesh-type
                bi-directional
                endpoint-type
                source-endpoints
                destination-endpoints
                frame-size
                frame-length
                frame-load
                frames
            ";

            key "name";
            leaf name {
                type t:config-list-key;
                description "The unique name of a traffic group";
            }
            leaf endpoint-type {
                description "The endpoints that this traffic group will use to generate traffic-stream objects.
                If endpoint-type is PORTS then the following applies:
                    Frames specified at the traffic-groups level will be carried forward over to every traffic-streams object that is generated.
               
                If endpoint-type is DEVICES-xxx then the following applies:
                    The server will first generate a list of frames based on the encapsulation selected.
                    Frames specified at the traffic-groups level will be carried forward over to every traffic-streams object that is generated.
                ";
                mandatory true;
                type enumeration {
                    enum PORTS;
                    enum DEVICES-ETHERNET;
                    enum DEVICES-VLAN;
                    enum DEVICES-IPV4;
                    enum DEVICES-IPV6;
                }
            }
            leaf bi-directional {
                type boolean;
                default false;
                description "If true then traffic-streams objects will be generated from destination DEVICES to source DEVICES.";
                when "../endpoint-type != PORTS";
            }
            leaf mesh-type {
                description "If true then traffic-streams objects will be generated from every destination DEVICES to every source DEVICES.";
                default "ONE_TO_ONE";
                type enumeration {
                    enum ONE_TO_ONE;
                    enum FULL_MESHED;
                }
                when "../endpoint-type != PORTS";
            }
            leaf-list source-ports {
                when "../endpoint-type = PORTS";
                type leafref {
                    path "../../ports/name";
                }
            }
            leaf-list destination-ports {
                when "../endpoint-type = PORTS";
                type leafref {
                    path "../../ports/name";
                }
            }
            leaf-list source-devices {
                when "../endpoint-type != PORTS";
                type union {
                    type leafref {
                        path "../../../device-groups/name";
                    }
                    type leafref {
                        path "../../../device-groups/devices/name";
                    }
                    type leafref {
                        path "../../../device-groups/devices/protocols/name";
                    }
                }
            }
            leaf-list destination-devices {
                when "../endpoint-type != PORTS";
                type union {
                    type leafref {
                        path "../../../device-groups/name";
                    }
                    type leafref {
                        path "../../../device-groups/devices/name";
                    }
                    type leafref {
                        path "../../../device-groups/devices/protocols/name";
                    }
                }
            }
            list frames {
                key "name";
                description "List of user defined frames. 
				Frames that are generated as part of the traffic-streams will overwrite any user defined frame leafs 
				that are part of the learned info due to the endpoint-type.";
                leaf name {
                    type t:config-list-key;
                }
                uses traffic-frame-group-top;
            }
            uses traffic-frame-options-group {
                description "Allows a user to set traffic options that will be used as a template during generation of traffic-streams.";
            }

            list traffic-streams {
                e:server-generated {
					description "The first attempt to access traffic-streams will cause the server to populate the list.";
				}
                key "name";
                leaf name {
                    e:server-generated;
                    type t:config-list-key;
                    description "Server should generate names using the following pattern: TrafficGroupName-SourceDevicesName-TransmitPortName";
                }
                leaf transmit-port {
                    config false;
                    description "The transmit port that this traffic stream object will be hosted on.";
                    type leafref {
                        path "../../../ports/name";
                    }
                }
                list frames {
                    key "name";
                    description "List of generated frames as defined by the endpoint-type.";
                    leaf name {
                        e:server-generated;
                        type t:config-list-key;
                    }
                    uses traffic-frame-group-top;
                }	
                uses traffic-frame-options-group {
                    description "Allows a user to customize traffic options on a per transmit port basis.";
                }		
            }
        }
        action traffic-groups-control {
            description
            "Control one or more traffic groups.
            An empty list signifies that all traffic groups will be started.";

            input {
                leaf-list traffic-groups {
                    type leafref {
                        path "../../traffic-groups/name";
                    }
                    description "A list of traffic group names";
                }
                leaf mode {
                    description "Specifies the action to be taken.";
                    type enumeration {
                        enum START;
                        enum STOP;
                    }
                    default "START";
                }
            }
            output {
                uses t:errata-group {
                    description "A list of traffic group resources that failed to start.
                    An empty list signifies that all traffic groups successfully started.";
                }
            }
        }
    }
}
