submodule openhltest-port {

    yang-version "1.1";
    belongs-to "openhltest" {
		prefix "oht";
	}

    import openhltest-types {
        prefix t;
    }
	
    organization
      "OpenHlTest working group";
    contact
      "OpenHlTest working group";
    description
      "This module describes a collection of abstract test ports
	  and associated rpcs. An abstract test port should be as 
	  minimal as possible.";

    revision 2017-11-02 {
        description
          "Initial revision.";
        reference
          "0.0.1";
    }

    grouping port-top {
        description
          "A grouping of abstract test ports";

		list ports {
			key "name";
			description
			"A list of abstract test ports";

			leaf name {
				type t:config-list-key;
				description
				"The unique name of an abstract test port";
			}	
		}				

		action connect-ports {
			description
			"Connect abstract test ports to physical hardware test ports and/or 
			virtual machine test ports";
			input {
				list port-map {
					key "port-name";
					leaf port-name {
						description "The name of an abstract test port";
						type t:config-list-key;
					}
					uses t:chassis-card-port-group;
				}
			}
			output {
				uses t:errata-group;
			}
		}
		action disconnect-ports {
			description
			"Disconnect abstract test ports from any connected
			physical hardware test ports and/or virtual machine test ports";
			input {
				leaf-list port-names {
					description "A list of abstract test port names. Names can also be regex";
					type t:config-list-key;
				}
			}
			output {
				uses t:errata-group;
			}
		}
	}
}
