submodule openhltest-layer1-twenty-five-gig {
  yang-version 1.1;
  belongs-to openhltest {
    prefix oht;
  }

  organization
    "OpenHlTest working group";
  contact
    "OpenHlTest working group";
  description
    "This submodule describes the 10 gigabit physical layer1 settings.";

  revision 2017-11-02 {
    description
      "Initial revision.";
    reference
      "0.0.1";
  }

  grouping layer1-twenty-five-gig-group {
    description
      "";
    container twenty-five-gig {
      description
        "";
      leaf advertise-ieee {
        type boolean;
        default "true";
        description
          "";
      }
    }
  }
}
