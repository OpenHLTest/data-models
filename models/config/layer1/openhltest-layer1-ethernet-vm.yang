submodule openhltest-layer1-ethernet-vm {

    belongs-to openhltest-layer1 {
        prefix "oht";
    }

    organization
      "tgn.org";
    contact
      admin@tgn.org;
    description
      "Layer1 definitions";

    revision 2017-09-20 {
        description
          "Initial revision.";
        reference
          "0.0.1";
    }
    
    grouping ethernet-vm-config {
        leaf auto-instrumentation {
            type enumeration {
                enum END_OF_FRAME;
                enum FLOATING;
            }
            default FLOATING;
        }
        leaf enable-ppm {
            type boolean;
        }
        leaf ppm {
            type int32; 
        }
        leaf loopback {
            type boolean;
        }
        leaf speed {
            type enumeration {
                enum ONE_HUNDRED_M;
                enum ONE_G;
                enum TWO_G;
                enum THREE_G;
                enum FOUR_G;
                enum FIVE_G;
                enum SIX_G,;
                enum SEVEN_G;
                enum EIGHT_G;
                enum NINE_G;
                enum TEN_G;
                enum TWENTY_G;
                enum TWENTY_FIVE_G;
                enum THIRTY_G;
                enum FORTY_G;
                enum FIFTY_G;
            }
            default ONE_G;
        }
    }
}
