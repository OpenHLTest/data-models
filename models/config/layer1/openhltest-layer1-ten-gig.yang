submodule openhltest-layer1-ten-gig {
  yang-version 1.1;
  belongs-to openhltest {
    prefix oht;
  }

  organization
    "OpenHlTest working group";
  contact
    "OpenHlTest working group";
  description
    "This submodule describes the 10 gigabit physical layer1 settings.";

  revision 2017-11-02 {
    description
      "Initial revision.";
    reference
      "0.0.1";
  }

  grouping layer1-ten-gig-copper-group {
    description
      "";
    container ten-gig-copper {
      description
        "";
      leaf advertise-ieee {
        type boolean;
        default "true";
        description
          "";
      }
    }
  }

  grouping layer1-ten-gig-fiber-group {
    description
      "";
    container ten-gig-fiber {
      description
        "";
      leaf advertise-ieee {
        type boolean;
        default "true";
        description
          "";
      }
    }
  }
}
