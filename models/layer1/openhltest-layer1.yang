module openhltest-layer1 {

    yang-version "1";
    namespace "http://openhltest.net/yang/layer1";
    prefix "oht";

    import openhltest-port {
        prefix p;
    }
    include openhltest-layer1-ethernet;
    include openhltest-layer1-ethernet-vm;

    organization
      "OpenHlTest working group";
    contact
      "OpenHlTest working group";
    description
      "This module describes abstract layer1 models.";

    revision 2017-11-02 {
        description
          "Initial revision.";
        reference
          "0.0.1";
    }

    grouping layer1-top {
        description
          "A grouping of abstract layer1 definitions";

        list layer1 {
            key "name";
            description
              "A list of abstract layer1 definitions";

            leaf name {
                type string;
                description
                  "The unique name of the layer1 definition";
            }
            leaf-list port-references {
                description
                  "A list of abstract port references";
                type leafref {
                    path "/p:port/p:name";
                }
            }
            leaf config-type {
                description "Determines which detailed layer1 conditional container is active";
                type enumeration {
                    enum ETHERNET;
                    enum ETHERNET_VM;
                    enum ETHERNET_IMPAIRMENT;
                    enum TEN_GIG;
                    enum FORTY_GIG;
                    enum HUNDRED_GIG;
                    enum FOUR_HUNDRED_GIG;
                    enum ATM;
                    enum POS;
                }
                default ETHERNET;
            }
            container ethernet {
                description "The conditional container for ethernet
                detailed layer1 information";
                when "../config-type = ETHERNET";
                uses ethernet-config;
            }
            container ethernet-vm {
                description "The conditional container for ethernet virtual machine 
                detailed layer1 information";
                when "../config-type = ETHERNET_VM";
                uses ethernet-vm-config;
            }
        }
    }

    uses layer1-top;
}
