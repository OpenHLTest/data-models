submodule openhltest-traffic-groups-statistics {

    yang-version "1.1";
    belongs-to "openhltest" {
		prefix "oht";
	}

    import openhltest-types {
        prefix t;
    }

    organization
      "OpenHlTest working group";
    contact
      "OpenHlTest working group";
    description
      "This module describes a YANG model for 
       abstract test port statistics.";

    revision 2017-11-02 {
        description
          "Initial revision.";
        reference
          "0.0.1";
    }

    grouping traffic-groups-statistics-top {
        description
          "A grouping of Traffic Group statistics";

		list device-traffic {
			config false;
			key "name";

            leaf name {
                description "Device Traffic name";
                type t:config-list-key;
            }
            leaf tx-frames {
                config false;
                type uint64;
                description
                  "The total number of frames transmitted on the port.
                  Empty if the abstract port is not connected to a test port.";
            }
            leaf rx-frames {
                config false;
                type uint64;
                description
                  "The total number of frames received on the the port.
                  Empty if the abstract port is not connected to a test port.";
            }
            leaf tx-frame-rate {
                config false;
                type uint64;
                description
                  "Total number of frames transmitted over the last 1-second interval.
                  Empty if the abstract port is not connected to a test port.";
            }
            leaf rx-frame-rate {
                config false;
                type uint64;
                description
                  "Total number of frames received over the last 1-second interval.
                  Empty if the abstract port is not connected to a test port.";
            }
            leaf dropped-frames {
                config false;
                type uint64;
                description
                  "Total Number of dropped frames during transit.
                  Empty if the abstract port is not connected to a test port.";
            }
            leaf tx-bit-count {
                config false;
                type uint64;
                description
                  "The total number of bits transmitted on the port.
                  Empty if the abstract port is not connected to a test port.";
            }
            leaf rx-bit-count {
                config false;
                type uint64;
                description
                  "The total number of bits received on the the port.
                  Empty if the abstract port is not connected to a test port.";
            }
            
            leaf tx-bit-rate {
                config false;
                type uint64;
                description
                  "Total number of bits transmitted over the last 1-second interval.
                  Empty if the abstract port is not connected to a test port.";
            }
            leaf rx-bit-rate {
                config false;
                type uint64;
                description
                  "Total number of bits received over the last 1-second interval.
                  Empty if the abstract port is not connected to a test port.";
            }
            leaf tx-byte-count {
                config false;
                type uint64;
                description
                  "The total number of bytes transmitted on the port.
                  Empty if the abstract port is not connected to a test port.";
            }
            leaf rx-byte-count {
                config false;
                type uint64;
                description
                  "The total number of bytes received on the the port.
                  Empty if the abstract port is not connected to a test port.";
            }
            
            leaf tx-byte-rate {
                config false;
                type uint64;
                description
                  "Total number of bytes transmitted over the last 1-second interval.
                  Empty if the abstract port is not connected to a test port.";
            }
            leaf rx-byte-rate {
                config false;
                type uint64;
                description
                  "Total number of bytes received over the last 1-second interval.
                  Empty if the abstract port is not connected to a test port.";
            }
            list port {
                key "name";
                leaf name {
                    description "Test Port name";
                    type t:config-list-key;
                }
                leaf tx-frames {
                    config false;
                    type uint64;
                    description
                      "The total number of frames transmitted on the port.
                      Empty if the abstract port is not connected to a test port.";
                }
                leaf rx-frames {
                    config false;
                    type uint64;
                    description
                      "The total number of frames received on the the port.
                      Empty if the abstract port is not connected to a test port.";
                }
                leaf tx-frame-rate {
                    config false;
                    type uint64;
                    description
                      "Total number of frames transmitted over the last 1-second interval.
                      Empty if the abstract port is not connected to a test port.";
                }
                leaf rx-frame-rate {
                    config false;
                    type uint64;
                    description
                      "Total number of frames received over the last 1-second interval.
                      Empty if the abstract port is not connected to a test port.";
                }
                leaf dropped-frames {
                    config false;
                    type uint64;
                    description
                      "Total Number of dropped frames during transit.
                      Empty if the abstract port is not connected to a test port.";
                }
                leaf tx-bit-count {
                    config false;
                    type uint64;
                    description
                      "The total number of bits transmitted on the port.
                      Empty if the abstract port is not connected to a test port.";
                }
                leaf rx-bit-count {
                    config false;
                    type uint64;
                    description
                      "The total number of bits received on the the port.
                      Empty if the abstract port is not connected to a test port.";
                }
                
                leaf tx-bit-rate {
                    config false;
                    type uint64;
                    description
                      "Total number of bits transmitted over the last 1-second interval.
                      Empty if the abstract port is not connected to a test port.";
                }
                leaf rx-bit-rate {
                    config false;
                    type uint64;
                    description
                      "Total number of bits received over the last 1-second interval.
                      Empty if the abstract port is not connected to a test port.";
                }
                leaf tx-byte-count {
                    config false;
                    type uint64;
                    description
                      "The total number of bytes transmitted on the port.
                      Empty if the abstract port is not connected to a test port.";
                }
                leaf rx-byte-count {
                    config false;
                    type uint64;
                    description
                      "The total number of bytes received on the the port.
                      Empty if the abstract port is not connected to a test port.";
                }
                
                leaf tx-byte-rate {
                    config false;
                    type uint64;
                    description
                      "Total number of bytes transmitted over the last 1-second interval.
                      Empty if the abstract port is not connected to a test port.";
                }
                leaf rx-byte-rate {
                    config false;
                    type uint64;
                    description
                      "Total number of bytes received over the last 1-second interval.
                      Empty if the abstract port is not connected to a test port.";
                }
            }
        }
    }
}
