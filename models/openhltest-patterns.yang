module openhltest-patterns {
  yang-version 1.1;
  namespace "http://openhltest.org/yang/patterns";
  prefix oht;

  organization
    "OpenHlTest working group";
  contact
    "OpenHlTest working group";
  description
    "This module defines value patterns specific to the OpenHLTest models.";

  revision 2018-02-01 {
    description
      "Initial revision.";
    reference
      "0.0.1";
  }

  grouping base-pattern-group {
    description
      "Base patterns for types such as decimal, ipv4, mac, ipv6
       The pattern is dependent on the re-match() function which allows this pattern group to be extended by models based on the type.
       Models will create a container which will use a pattern-group. The container will then refine the pattern-format default.
       The pattern group is extended in this module to provide some common pattern types such as decimal, mac, ipv4, ipv6.
      ";
    leaf pattern-type {
      type enumeration {
        enum SINGLE {
          description
            "";
        }
        enum INCREMENT {
          description
            "";
        }
        enum DECREMENT {
          description
            "";
        }
        enum RANDOM {
          description
            "";
        }
        enum VALUE_LIST {
          description
            "";
        }
      }
      default "SINGLE";
      description
        "The selected pattern from the possible pattern types.";
    }
    leaf pattern-format {
      type string;
      config false;
      description
        "The format of the pattern.
         This will almost always be a regular expression.
         It is used to determine the validity of the values being set in the child leaf nodes of the pattern.";
    }
    leaf single {
      when '../pattern-type = SINGLE';
      type string;
      must 're-match(single, ../pattern-format)';
      description
        "The value of the single pattern";
    }
    container increment {
      when '../pattern-type = INCREMENT';
      description
        "The values that make up the increment pattern";
      leaf start {
        type string;
        must 're-match(start, ../pattern-format)';
        description
          "The start value of the increment pattern";
      }
      leaf step {
        type string;
        must 're-match(step, ../pattern-format)';
        description
          "The step value of the increment pattern";
      }
    }
    container decrement {
      when '../pattern-type = DECREMENT';
      description
        "";
      leaf start {
        type string;
        must 're-match(start, ../pattern-format)';
        description
          "The start value of the decrement pattern";
      }
      leaf step {
        type string;
        must 're-match(step, ../pattern-format)';
        description
          "The step value of the decrement pattern";
      }
    }
    container random {
      when '../pattern-type = RANDOM';
      description
        "The repeatable random pattern.";
      leaf min {
        type string;
        must 're-match(min, ../pattern-format)';
        description
          "The minimum random value of the random pattern";
      }
      leaf max {
        type string;
        must 're-match(max, ../pattern-format)';
        description
          "The maximum random value of the random pattern";
      }
      leaf step {
        type string;
        must 're-match(step, ../pattern-format)';
        description
          "The step value of the random pattern";
      }
      leaf seed {
        type uint32;
        description
          "The seed value of the random pattern";
      }
    }
    leaf-list value-list {
      when '../pattern-type = VALUE_LIST';
      type string;
      must 're-match(value-list, ../pattern-format)';
      description
        "The value list pattern takes a list of values that will be repeated if they do not meet or exceed the count";
    }
  }

  grouping traffic-pattern-extension {
    description
      "Traffic extensions that can be applied to any pattern grouping.";
    leaf count {
      type int32;
      default "1";
      description
        "The count of the pattern";
    }
    leaf statistic-tracking {
      type boolean;
      default "false";
      description
        "Flag to identify the parent pattern container as a candidate for statistic tracking";
    }
  }

  grouping hex-pattern-group {
    description
      "";
    uses base-pattern-group {
      refine "pattern-format" {
        default "[0-9a-f]+";
      }
    }
  }

  grouping bool-pattern-group {
    description
      "";
    uses base-pattern-group {
      refine "pattern-format" {
        default "(true|false)";
      }
    }
  }

  grouping int-32-pattern-group {
    description
      "";
    uses base-pattern-group {
      refine "pattern-format" {
        default "(-?(1\\d{0,9}|2(0\\d{8}|1[0-3]\\d{7}|14[0-6]\\d{6}|147[0-3]\\d{5}|1474[0-7]\\d{4}|14748[0-2]\\d{3}|147483[0-5]\\d{2}|1474836[0-3]\\d|14748364[0-7])|[1-9]\\d{0,8})|0|-2147483648)";
      }
    }
  }

  grouping int-64-pattern-group {
    description
      "";
    uses base-pattern-group {
      refine "pattern-format" {
        default "^\\d+\\.?\\d{0,2}$";
      }
    }
  }

  grouping decimal-pattern-group {
    description
      "";
    uses base-pattern-group {
      refine "pattern-format" {
        default "^\\d+\\.?\\d{0,2}$";
      }
    }
  }

  grouping binary-pattern-group {
    description
      "";
    uses base-pattern-group {
      refine "pattern-format" {
        default "(1|0)";
      }
    }
  }

  grouping ethertype-pattern-group {
    description
      "";
    uses base-pattern-group {
      refine "pattern-format" {
        default "(0x0800|0x0806|0x86DD)";
      }
    }
  }

  grouping mac-pattern-group {
    description
      "";
    uses base-pattern-group {
      refine "pattern-format" {
        default "^([0-9A-Fa-f]{2}[:]){5}([0-9A-Fa-f]{2})$";
      }
    }
  }

  grouping ipv4-pattern-group {
    description
      "";
    uses base-pattern-group {
      refine "pattern-format" {
        default "^((25[0-5]|2[0-4][0-9]|[01]?[0-9][0-9]?)\\.){3}(25[0-5]|2[0-4][0-9]|[01]?[0-9][0-9]?)$";
      }
    }
  }

  grouping ipv6-pattern-group {
    description
      "";
    uses base-pattern-group {
      refine "pattern-format" {
        default "^(?=\\d{1,3}\\.\\d{1,3}\\.\\d{1,3}\\.\\d{1,3}$)(?:(?:25[0-5]|[12][0-4][0-9]|1[5-9][0-9]|[1-9]?[0-9])\\.?){4}$|(?=^(?:[0-9a-f]{0,4}:){2,7}[0-9a-f]{0,4}$)(?![^:]*::.+::[^:]*$)(?:(?=.*::.*)|(?=\\w+:\\w+:\\w+:\\w+:\\w+:\\w+:\\w+:\\w+))(?:(?:^|:)(?:[0-9a-f]{4}|[1-9a-f][0-9a-f]{0,3})){0,8}(?:::(?:[0-9a-f]{1,4}(?:$|:)){0,6})?$";
      }
    }
  }

  grouping enum-pattern-group {
    description
      "An extended pattern-group that limits the number of patterns for enums.
       Modelers must refine the pattern-format default with a regex of valid enum choices.
       e.g.,
       refine pattern-format {
       default '(8100|88a8|9100|9200|9300)'
       }";
    leaf pattern-format {
      type string;
      config false;
      description
        "Refine this leaf value with a regex of valid enum choices";
    }
    leaf pattern-type {
      type enumeration {
        enum SINGLE {
          description
            "";
        }
        enum VALUE_LIST {
          description
            "";
        }
      }
      default "SINGLE";
      description
        "";
    }
    leaf single {
      when '../pattern-type = SINGLE';
      type string;
      must 're-match(single, ../pattern-format)';
      description
        "";
    }
    leaf-list value-list {
      when '../pattern-type = VALUE_LIST';
      type string;
      must 're-match(value-list, ../pattern-format)';
      description
        "";
    }
  }

  grouping string-pattern-group {
    description
      "Supports the ability to specify a string pattern in addition to single values.\n";
    leaf pattern-format {
      type string;
      config false;
      description
        "Refine this leaf value with a regex";
    }
    leaf pattern-type {
      type enumeration {
        enum SINGLE {
          description
            "";
        }
        enum STRING {
          description
            "";
        }
        enum VALUE_LIST {
          description
            "";
        }
      }
      default "SINGLE";
      description
        "";
    }
    leaf single {
      when '../pattern-type = SINGLE';
      type string;
      must 're-match(single, ../pattern-format)';
      description
        "";
    }
    leaf string {
      when '../pattern-type = STRING';
      type string;
      description
        "Vendor specific string patterns";
    }
    leaf-list value-list {
      when '../pattern-type = VALUE_LIST';
      type string;
      must 're-match(value-list, ../pattern-format)';
      description
        "";
    }
  }
}
