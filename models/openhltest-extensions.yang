module openhltest-extensions {
  yang-version 1.1;
  namespace "http://openhltest.org/yang/extensions";
  prefix oht;

  organization
    "OpenHlTest working group";
  contact
    "OpenHlTest working group";
  description
    "This module defines extensions specific to OpenHLTest models.";

  revision 2018-08-22 {
    description
      "Initial revision.";
    reference
      "0.0.1";
  }

  extension server-generated {
    description
      "The existence of this statement in a list that is configurable
       indicates that the list of items is generated by the server and the client cannot add or remove the items from the list.
       This should indicate to any pyang code generator to not generate add or remove functionality.";
  }

  extension ixia-not-supported {
    description
      "The existence of this statement in a container, list, leaf indicates that the feature is not supported by Ixia.
       The pyang code generator should generate code to return an error if used on an Ixia test platform.";
  }

  extension spirent-not-supported {
    description
      "The existence of this statement in a container, list, leaf indicates that the feature is not supported by Spirent.
       The pyang code generator should generate code to return an error if used on a Spirent test platform.";
  }
}
