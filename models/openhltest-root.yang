module openhltest-root {

    yang-version "1";
    namespace "http://openhltest.org/yang/root";
    prefix "oht";

    import openhltest-port {
        prefix p;
    }
    import openhltest-layer1 {
        prefix l;
    }
    import openhltest-statistics {
        prefix s;
    }

    organization
      "OpenHlTest working group";
    contact
      "OpenHlTest working group";
    description
      "This module aggregates all other top level modules.
	  If a view is created using pyang it will exclude rpc and notification elements.";

    revision 2017-11-02 {
        description
          "Initial revision.";
        reference
          "0.0.1";
    }

    grouping root-top {
        description
          "A top level aggregate of all other top level modules";

		uses p:port-top;
		uses l:layer1-top;
		uses s:statistics-top;
    }

    uses root-top;
}
